TestModule { test(0) } DEFINITIONS ::= BEGIN
    MyBool ::= BOOLEAN

    MyChoice ::= CHOICE {
        bitstring [0] EXPLICIT [APPLICATION 10] EXPLICIT BIT STRING,
        boolean BOOLEAN
    }

    MySequence ::= SEQUENCE {
        a BOOLEAN,
        b BOOLEAN OPTIONAL,
        c [UNIVERSAL 2] IMPLICIT BOOLEAN
    }
END
